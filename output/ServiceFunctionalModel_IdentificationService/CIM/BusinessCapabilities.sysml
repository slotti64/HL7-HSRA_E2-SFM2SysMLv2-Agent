package CIM_IS {

    package BusinessCapabilities {
        doc /* CIM-level Business Capabilities for the HL7 Identification Service (IS).
             * Models all service capabilities as use case usages, organized into two
             * capability groups: Identity Management and Query. Business scenarios
             * from SFM Section 3 are modeled as top-level use cases with subject,
             * actors, objectives, action steps, and sequencing. Normative operations
             * from SFM Section 4 are modeled as included use cases.
             * [ST-001, ST-004, ST-025, ST-026, ST-027] */

        /* ===================================================================
         * TOP-LEVEL SERVICE CAPABILITY
         * =================================================================== */

        part identificationService {
            doc /* The Identification Service provides a set of capabilities to manage
                 * and retrieve identifying information for various kinds of entities
                 * (people, organizations, devices, etc.) within and across
                 * organizations. [ST-001, ST-004] */

            /* =============================================================
             * IDENTITY MANAGEMENT CAPABILITIES (Section 4.3)
             * ============================================================= */

            include use case registerIdentity {
                doc /* Allows creation of an identity with a supplied set of property
                     * values, using an identifier supplied by the service consumer
                     * which is unique within the PolicyDomain for the EntityType.
                     * [ST-082, ST-083, ST-084, ST-085, ST-086, ST-087] */

                subject serviceInstance {
                    doc /* The Identification Service instance performing the registration. [ST-082] */
                    perform validateAndRegister;
                    perform checkForAutomatedLinks;
                }
                actor registrationClerk {
                    doc /* The registration clerk or external system supplying identity
                         * information and a locally assigned identifier. [ST-212, ST-216] */
                    perform supplyIdentityInformation;
                }
                objective {
                    doc /* Create a new identity instance with a consumer-supplied identifier
                         * that is unique within the PolicyDomain and EntityType scope. */
                }
                action supplyIdentityInformation;
                action validateAndRegister;
                action checkForAutomatedLinks;
                ref first start then supplyIdentityInformation;
                ref first supplyIdentityInformation then validateAndRegister;
                ref first validateAndRegister then checkForAutomatedLinks;
                ref first checkForAutomatedLinks then done;
            }

            include use case createIdentity {
                doc /* Allows creation of an identity instance with a list of property
                     * values where the identifier is generated by the service and
                     * returned to the service consumer. Used where the consumer cannot
                     * generate and supply its own local identifiers.
                     * [ST-088, ST-089, ST-090] */

                subject serviceInstance {
                    doc /* The Identification Service instance generating the identifier
                         * and creating the identity. [ST-088] */
                    perform generateIdentifierAndCreate;
                    perform checkForAutomatedLinks;
                }
                actor externalSystem {
                    doc /* The external system requesting identity creation without
                         * supplying its own identifier. [ST-216] */
                    perform supplyPropertyValues;
                }
                objective {
                    doc /* Create a new identity instance with a service-generated
                         * identifier and return it to the consumer. */
                }
                action supplyPropertyValues;
                action generateIdentifierAndCreate;
                action checkForAutomatedLinks;
                ref first start then supplyPropertyValues;
                ref first supplyPropertyValues then generateIdentifierAndCreate;
                ref first generateIdentifierAndCreate then checkForAutomatedLinks;
                ref first checkForAutomatedLinks then done;
            }

            include use case updateIdentityProperties {
                doc /* Allows addition and/or update of a set of property values
                     * for an identity specified by a unique identifier. The update
                     * qualifier specifies the mode (overwrite, valued, or unspecified).
                     * [ST-092, ST-093, ST-094, ST-095, ST-096] */

                subject serviceInstance {
                    doc /* The Identification Service instance applying the property update.
                         * [ST-092] */
                    perform applyPropertyUpdate;
                    perform evaluateMatchImpact;
                }
                actor registrationClerk {
                    doc /* The clerk providing updated property values and update mode.
                         * [ST-212, ST-056] */
                    perform specifyUpdateDetails;
                }
                objective {
                    doc /* Update the identifying properties of an existing identity instance
                         * according to the specified update mode. */
                }
                action specifyUpdateDetails;
                action applyPropertyUpdate;
                action evaluateMatchImpact;
                ref first start then specifyUpdateDetails;
                ref first specifyUpdateDetails then applyPropertyUpdate;
                ref first applyPropertyUpdate then evaluateMatchImpact;
                ref first evaluateMatchImpact then done;
            }

            include use case updateIdentityState {
                doc /* Changes the processing state of an identity (e.g., to inactive,
                     * active, or other states defined in appropriate organizational
                     * policies). All identity information is unchanged except for the
                     * state change.
                     * [ST-097, ST-098, ST-099, ST-100, ST-101, ST-102, ST-103, ST-104] */

                subject serviceInstance {
                    doc /* The Identification Service instance applying the state change.
                         * [ST-097] */
                    perform validateStateTransition;
                    perform applyStateChange;
                }
                actor serviceAdministrator {
                    doc /* The administrator requesting the state change with appropriate
                         * reason. [ST-215, ST-059, ST-062] */
                    perform requestStateChange;
                }
                objective {
                    doc /* Transition the identity to a new processing state while
                         * preserving all other identity information unchanged. */
                }
                action requestStateChange;
                action validateStateTransition;
                action applyStateChange;
                ref first start then requestStateChange;
                ref first requestStateChange then validateStateTransition;
                ref first validateStateTransition then applyStateChange;
                ref first applyStateChange then done;
            }

            include use case mergeIdentities {
                doc /* Allows merging two identities within a single PolicyDomain. The
                     * target identifier is the survivor; the source becomes deprecated.
                     * Empty identifying attributes in the target are filled from the
                     * source. Must be restricted to identities of the same EntityConcept.
                     * [ST-107, ST-108, ST-109, ST-110, ST-111, ST-112, ST-113, ST-114] */

                subject serviceInstance {
                    doc /* The Identification Service instance performing the merge.
                         * [ST-107] */
                    perform validateMergePreconditions;
                    perform performAttributeResolution;
                    perform deprecateSourceIdentity;
                    perform recordMergeAssociation;
                }
                actor identityResolutionClerk {
                    doc /* The identity resolution specialist requesting the merge of
                         * duplicate identity records. [ST-214, ST-052] */
                    perform designateSourceAndTarget;
                }
                objective {
                    doc /* Consolidate two identity instances representing the same
                         * real-world entity into a single surviving record, deprecating
                         * the source and filling empty target attributes from the source. */
                }
                action designateSourceAndTarget;
                action validateMergePreconditions;
                action performAttributeResolution;
                action deprecateSourceIdentity;
                action recordMergeAssociation;
                ref first start then designateSourceAndTarget;
                ref first designateSourceAndTarget then validateMergePreconditions;
                ref first validateMergePreconditions then performAttributeResolution;
                ref first performAttributeResolution then deprecateSourceIdentity;
                ref first deprecateSourceIdentity then recordMergeAssociation;
                ref first recordMergeAssociation then done;
            }

            include use case unmergeIdentities {
                doc /* Allows unmerging two previously merged identities. Reinstates the
                     * previously deprecated identity. The state of unmerged identities
                     * cannot be guaranteed valid; subsequent manual updates may be
                     * required to correct both entries.
                     * [ST-115, ST-116, ST-117, ST-118, ST-119, ST-120] */

                subject serviceInstance {
                    doc /* The Identification Service instance performing the unmerge.
                         * [ST-115] */
                    perform validateUnmergePreconditions;
                    perform reverseAssociation;
                    perform reinstateDeprecatedIdentity;
                }
                actor identityResolutionClerk {
                    doc /* The identity resolution specialist requesting the separation
                         * of previously merged records. [ST-214, ST-064] */
                    perform requestUnmerge;
                }
                objective {
                    doc /* Reverse a previous merge, reinstating the deprecated identity
                         * and removing the merge association. Manual review is expected
                         * after unmerge. */
                }
                action requestUnmerge;
                action validateUnmergePreconditions;
                action reverseAssociation;
                action reinstateDeprecatedIdentity;
                ref first start then requestUnmerge;
                ref first requestUnmerge then validateUnmergePreconditions;
                ref first validateUnmergePreconditions then reverseAssociation;
                ref first reverseAssociation then reinstateDeprecatedIdentity;
                ref first reinstateDeprecatedIdentity then done;
            }

            include use case linkIdentities {
                doc /* Allows linking of two identities. Linking can be carried out
                     * within a single PolicyDomain or across two different domains.
                     * Linked identities represent the same real-world entity and
                     * links are transitive by definition. Cross-EntityType linking
                     * is permitted but recommended only for the same EntityConcept.
                     * [ST-121, ST-122, ST-123, ST-124, ST-125, ST-126, ST-127, ST-128] */

                subject serviceInstance {
                    doc /* The Identification Service instance establishing the link.
                         * [ST-121] */
                    perform validateLinkPreconditions;
                    perform establishLink;
                    perform propagateTransitiveLinks;
                }
                actor identityResolutionClerk {
                    doc /* The identity resolution specialist or clinical user
                         * requesting the link. [ST-214, ST-213, ST-052] */
                    perform designateLinkPair;
                }
                objective {
                    doc /* Establish a link between two identity instances indicating
                         * they represent the same real-world entity, with both
                         * instances remaining active. */
                }
                action designateLinkPair;
                action validateLinkPreconditions;
                action establishLink;
                action propagateTransitiveLinks;
                ref first start then designateLinkPair;
                ref first designateLinkPair then validateLinkPreconditions;
                ref first validateLinkPreconditions then establishLink;
                ref first establishLink then propagateTransitiveLinks;
                ref first propagateTransitiveLinks then done;
            }

            include use case unlinkIdentity {
                doc /* Allows for the unlinking of two previously linked entities.
                     * Both identities must exist and be currently linked to each other.
                     * [ST-129, ST-130, ST-131, ST-132] */

                subject serviceInstance {
                    doc /* The Identification Service instance removing the link.
                         * [ST-129] */
                    perform validateUnlinkPreconditions;
                    perform removeLink;
                }
                actor identityResolutionClerk {
                    doc /* The identity resolution specialist requesting the unlink.
                         * [ST-214, ST-064] */
                    perform requestUnlink;
                }
                objective {
                    doc /* Remove the link between two identity instances that were
                         * previously linked. */
                }
                action requestUnlink;
                action validateUnlinkPreconditions;
                action removeLink;
                ref first start then requestUnlink;
                ref first requestUnlink then validateUnlinkPreconditions;
                ref first validateUnlinkPreconditions then removeLink;
                ref first removeLink then done;
            }

            include use case removeIdentityInstance {
                doc /* Allows for the complete removal of an identity instance from
                     * the service. The identity must exist, be in an appropriate
                     * state, and must not be linked to other entities. Removed records
                     * may be kept for audit trail purposes but are no longer findable.
                     * [ST-133, ST-134, ST-135, ST-136, ST-137, ST-138, ST-139] */

                subject serviceInstance {
                    doc /* The Identification Service instance performing the removal.
                         * [ST-133] */
                    perform validateRemovalPreconditions;
                    perform performRemoval;
                }
                actor serviceAdministrator {
                    doc /* The privileged administrator requesting identity removal.
                         * This capability is restricted to users with specified
                         * privileges. [ST-215, ST-139, ST-192] */
                    perform requestRemoval;
                }
                objective {
                    doc /* Permanently remove an identity instance from the service so
                         * it is no longer findable by any user, while optionally
                         * retaining audit records. */
                }
                action requestRemoval;
                action validateRemovalPreconditions;
                action performRemoval;
                ref first start then requestRemoval;
                ref first requestRemoval then validateRemovalPreconditions;
                ref first validateRemovalPreconditions then performRemoval;
                ref first performRemoval then done;
            }

            /* =============================================================
             * QUERY CAPABILITIES (Section 4.4)
             * ============================================================= */

            include use case getAllInformationForIdentity {
                doc /* Retrieves all information for an identity known by the service
                     * (properties, status, etc.). A specific unique identifier is input
                     * qualified by PolicyDomain and EntityType. If the identity has been
                     * merged into another, a warning is returned with the surviving
                     * identifier.
                     * [ST-140, ST-141, ST-142, ST-143, ST-144, ST-145] */

                subject serviceInstance {
                    doc /* The Identification Service instance retrieving identity
                         * information. [ST-140] */
                    perform resolveIdentifier;
                    perform retrieveAllProperties;
                }
                actor clinicalUser {
                    doc /* The clinical user or external system requesting full identity
                         * information. [ST-213, ST-216] */
                    perform specifyIdentifier;
                }
                objective {
                    doc /* Retrieve the complete set of property values, status, and
                         * related information for a specific known identity. */
                }
                action specifyIdentifier;
                action resolveIdentifier;
                action retrieveAllProperties;
                ref first start then specifyIdentifier;
                ref first specifyIdentifier then resolveIdentifier;
                ref first resolveIdentifier then retrieveAllProperties;
                ref first retrieveAllProperties then done;
            }

            include use case findIdentitiesByProperty {
                doc /* Given a partially populated semantic signifier and other search
                     * filter criteria, searches for matching identities. Search
                     * qualifiers enable directing search behavior. Outputs include a
                     * quality of match for each result.
                     * [ST-146, ST-147, ST-148, ST-149] */

                subject serviceInstance {
                    doc /* The Identification Service instance performing the search.
                         * [ST-146] */
                    perform executePropertySearch;
                    perform rankResultsByMatchQuality;
                }
                actor registrationClerk {
                    doc /* The registration clerk or clinical user supplying search
                         * properties and optional qualifiers. [ST-212, ST-213] */
                    perform specifySearchCriteria;
                }
                objective {
                    doc /* Find identity instances matching the supplied identifying
                         * properties, ranked by quality of match. */
                }
                action specifySearchCriteria;
                action executePropertySearch;
                action rankResultsByMatchQuality;
                ref first start then specifySearchCriteria;
                ref first specifySearchCriteria then executePropertySearch;
                ref first executePropertySearch then rankResultsByMatchQuality;
                ref first rankResultsByMatchQuality then done;
            }

            include use case listLinkedIdentities {
                doc /* Given an identifier, lists all other entities that are linked
                     * to the identity, optionally constrained within one or more
                     * PolicyDomains.
                     * [ST-150, ST-151, ST-152, ST-153, ST-154] */

                subject serviceInstance {
                    doc /* The Identification Service instance retrieving linked identities.
                         * [ST-150] */
                    perform validateIdentityExists;
                    perform retrieveLinkedIdentities;
                }
                actor identityResolutionClerk {
                    doc /* The identity resolution clerk or clinical user requesting the
                         * list of linked identities. [ST-214, ST-213, ST-064] */
                    perform specifyIdentityAndScope;
                }
                objective {
                    doc /* Retrieve all identities linked to a specified identity,
                         * optionally filtered by PolicyDomain. */
                }
                action specifyIdentityAndScope;
                action validateIdentityExists;
                action retrieveLinkedIdentities;
                ref first start then specifyIdentityAndScope;
                ref first specifyIdentityAndScope then validateIdentityExists;
                ref first validateIdentityExists then retrieveLinkedIdentities;
                ref first retrieveLinkedIdentities then done;
            }

            include use case requestIdentityUpdateNotifications {
                doc /* The service consumer lodges a request to be notified of changes
                     * to information for a specific identity or identities of a specific
                     * type and/or domain combination. Effectively a subscription operation.
                     * [ST-155, ST-156, ST-157, ST-158, ST-159] */

                subject serviceInstance {
                    doc /* The Identification Service instance managing the notification
                         * subscription. [ST-155] */
                    perform validateSubscriptionCriteria;
                    perform establishSubscription;
                }
                actor externalSystem {
                    doc /* The external system subscribing to identity update
                         * notifications. [ST-216] */
                    perform specifyNotificationCriteria;
                }
                objective {
                    doc /* Register a standing request to receive notifications when
                         * identity information matching the specified criteria changes. */
                }
                action specifyNotificationCriteria;
                action validateSubscriptionCriteria;
                action establishSubscription;
                ref first start then specifyNotificationCriteria;
                ref first specifyNotificationCriteria then validateSubscriptionCriteria;
                ref first validateSubscriptionCriteria then establishSubscription;
                ref first establishSubscription then done;
            }

            include use case updateNotificationSubscription {
                doc /* The service consumer provides an update to a previously submitted
                     * notification request, including modification of criteria or
                     * cancellation of the request.
                     * [ST-160, ST-161, ST-162, ST-163] */

                subject serviceInstance {
                    doc /* The Identification Service instance updating the subscription.
                         * [ST-160] */
                    perform validateUpdateCriteria;
                    perform applySubscriptionUpdate;
                }
                actor externalSystem {
                    doc /* The external system modifying or cancelling its notification
                         * subscription. [ST-216] */
                    perform specifySubscriptionChanges;
                }
                objective {
                    doc /* Modify or cancel an existing notification subscription. */
                }
                action specifySubscriptionChanges;
                action validateUpdateCriteria;
                action applySubscriptionUpdate;
                ref first start then specifySubscriptionChanges;
                ref first specifySubscriptionChanges then validateUpdateCriteria;
                ref first validateUpdateCriteria then applySubscriptionUpdate;
                ref first applySubscriptionUpdate then done;
            }

            include use case notifyIdentityUpdates {
                doc /* The service produces a notification of an update made to any
                     * information relating to a specific identity or identities within
                     * a PolicyDomain and/or EntityType, as previously requested via a
                     * notification subscription. Effectively a publication operation.
                     * [ST-164, ST-165, ST-166, ST-167] */

                subject serviceInstance {
                    doc /* The Identification Service instance producing the notification.
                         * [ST-164] */
                    perform detectRelevantChange;
                    perform produceNotification;
                }
                actor externalSystem {
                    doc /* The subscribed external system receiving the notification.
                         * [ST-216] */
                    perform receiveNotification;
                }
                objective {
                    doc /* Deliver a notification of identity information changes to
                         * subscribers who have previously registered interest. */
                }
                action detectRelevantChange;
                action produceNotification;
                action receiveNotification;
                ref first start then detectRelevantChange;
                ref first detectRelevantChange then produceNotification;
                ref first produceNotification then receiveNotification;
                ref first receiveNotification then done;
            }
        }

        /* ===================================================================
         * BUSINESS SCENARIOS (Section 3 - Non-normative)
         * These model the real-world workflows described in the SFM to provide
         * context for how the normative capabilities are composed in practice.
         * Each use case maps its action steps to the SFM swimlane with explicit
         * performer assignments for the human actor, HIS, IS, and (where
         * applicable) XIS.
         * =================================================================== */

        /* -----------------------------------------------------------
         * Single-Domain Scenarios (Section 3.2)
         * ----------------------------------------------------------- */

        part singleDomainScenarios {
            doc /* Business scenarios within a single PolicyDomain, illustrating
                 * common identity management workflows in a hospital setting.
                 * These are non-normative and offered for explanatory purposes.
                 * Performers: human actors, HIS (Hospital Information System),
                 * and IS (Identification Service).
                 * [ST-047, ST-202] */

            /* --- Scenario 1: Create a New Patient (SFM 3.2.1) --- */

            include use case createNewPatient {
                doc /* Adam Everyman enters the hospital for outpatient surgery.
                     * Carol Clerk searches by name+address, then by old address —
                     * not found. Carol treats Adam as a new patient, gathers
                     * demographics, and registers the identity via HIS and IS.
                     * [ST-048, ST-049, ST-050, ST-051] */

                subject hospitalInformationSystem {
                    doc /* The clinical system mediating between the clerk and the
                         * Identification Service. [ST-045] */
                    perform relaySearchToIS_initial;
                    perform reportNoRecordFound_initial;
                    perform relaySearchToIS_broader;
                    perform reportNoRecordFound_broader;
                    perform relayRegistrationToIS;
                    perform confirmPatientRegistered;
                }
                actor registrationClerk {
                    doc /* Carol Clerk, a registration clerk. [ST-212, ST-048] */
                    perform searchByNameAndAddress;
                    perform searchWithOldAddress;
                    perform gatherDemographicsAndCreate;
                }
                actor identificationService {
                    doc /* The Identification Service instance managing identities
                         * within the hospital's PolicyDomain. [ST-001] */
                    perform returnEmptyList_initial;
                    perform returnEmptyList_broader;
                    perform acknowledgeRegistration;
                }
                objective {
                    doc /* Verify whether a patient already exists in the identity registry;
                         * if not found, create a new identity instance for the patient. */
                }
                /* Step 1: Carol searches Adam by name + address */
                action searchByNameAndAddress;
                /* Step 2: HIS calls FindIdentityByProperty(Person, Name, Address) on IS */
                action relaySearchToIS_initial;
                /* Step 3: IS returns empty list */
                action returnEmptyList_initial;
                /* Step 4: HIS reports no record found to Carol */
                action reportNoRecordFound_initial;
                /* Step 5: Carol searches Adam with additional info (old address) */
                action searchWithOldAddress;
                /* Step 6: HIS calls FindIdentityByProperty(Person, Adam, OldAddress) on IS */
                action relaySearchToIS_broader;
                /* Step 7: IS returns empty list */
                action returnEmptyList_broader;
                /* Step 8: HIS reports no record found to Carol */
                action reportNoRecordFound_broader;
                /* Step 9: Carol gathers demographics, creates new patient */
                action gatherDemographicsAndCreate;
                /* Step 10: HIS calls RegisterIdentity(Person, ID, Adam) on IS */
                action relayRegistrationToIS;
                /* Step 11: IS returns acknowledgement */
                action acknowledgeRegistration;
                /* Step 12: HIS confirms new patient registered to Carol */
                action confirmPatientRegistered;
                ref first start then searchByNameAndAddress;
                ref first searchByNameAndAddress then relaySearchToIS_initial;
                ref first relaySearchToIS_initial then returnEmptyList_initial;
                ref first returnEmptyList_initial then reportNoRecordFound_initial;
                ref first reportNoRecordFound_initial then searchWithOldAddress;
                ref first searchWithOldAddress then relaySearchToIS_broader;
                ref first relaySearchToIS_broader then returnEmptyList_broader;
                ref first returnEmptyList_broader then reportNoRecordFound_broader;
                ref first reportNoRecordFound_broader then gatherDemographicsAndCreate;
                ref first gatherDemographicsAndCreate then relayRegistrationToIS;
                ref first relayRegistrationToIS then acknowledgeRegistration;
                ref first acknowledgeRegistration then confirmPatientRegistered;
                ref first confirmPatientRegistered then done;
            }

            /* --- Scenario 2a: Link Identities (SFM 3.2.2a) --- */

            include use case linkIdentities {
                doc /* Nancy Nightingale discovers two records for Adam that appear
                     * to be the same person. She requests the HIS to link the newer
                     * entity to the older one. Both remain active; the newer becomes
                     * an alias for the older. [ST-052, ST-053] */

                subject hospitalInformationSystem {
                    doc /* The clinical system mediating between the user and the
                         * Identification Service. [ST-045] */
                    perform relaySearchToIS;
                    perform displayPersonList;
                    perform relayLinkRequestToIS;
                    perform confirmIdentityLinked;
                }
                actor clinicalUser {
                    doc /* Nancy Nightingale, discharge nurse, discovering duplicate
                         * records. [ST-213, ST-052] */
                    perform searchForPatient;
                    perform reviewListAndDecideSamePerson;
                    perform requestLinkNewerToOlder;
                }
                actor identificationService {
                    doc /* The Identification Service instance. [ST-001] */
                    perform returnPersonListWithTwoAdams;
                    perform acknowledgeLinking;
                }
                objective {
                    doc /* Link two identity records representing the same real-world
                         * entity, maintaining both as active with a link association. */
                }
                /* Step 1: Nancy searches Adam */
                action searchForPatient;
                /* Step 2: HIS calls FindIdentityByProperty(Adam) on IS */
                action relaySearchToIS;
                /* Step 3: IS returns person list including two Adams */
                action returnPersonListWithTwoAdams;
                /* Step 4: HIS displays person list to Nancy */
                action displayPersonList;
                /* Step 5: Nancy reviews list, decides two Adams are same person */
                action reviewListAndDecideSamePerson;
                /* Step 6: Nancy requests link newer Adam to older Adam */
                action requestLinkNewerToOlder;
                /* Step 7: HIS calls LinkIdentities(Person, newerAdam, Person, olderAdam) on IS */
                action relayLinkRequestToIS;
                /* Step 8: IS returns acknowledgement */
                action acknowledgeLinking;
                /* Step 9: HIS confirms identity linked to Nancy */
                action confirmIdentityLinked;
                ref first start then searchForPatient;
                ref first searchForPatient then relaySearchToIS;
                ref first relaySearchToIS then returnPersonListWithTwoAdams;
                ref first returnPersonListWithTwoAdams then displayPersonList;
                ref first displayPersonList then reviewListAndDecideSamePerson;
                ref first reviewListAndDecideSamePerson then requestLinkNewerToOlder;
                ref first requestLinkNewerToOlder then relayLinkRequestToIS;
                ref first relayLinkRequestToIS then acknowledgeLinking;
                ref first acknowledgeLinking then confirmIdentityLinked;
                ref first confirmIdentityLinked then done;
            }

            /* --- Scenario 2b: Merge Identities (SFM 3.2.2b) --- */

            include use case mergeIdentities {
                doc /* Alternative to linking: Nancy Nightingale discovers duplicate
                     * records and the hospital's policy calls for merging. The newer
                     * record is deprecated and only the surviving record is used
                     * going forward. [ST-054, ST-055] */

                subject hospitalInformationSystem {
                    doc /* The clinical system mediating between the user and the
                         * Identification Service. [ST-045] */
                    perform relaySearchToIS;
                    perform displayPersonList;
                    perform relayMergeRequestToIS;
                    perform confirmIdentityMerged;
                }
                actor clinicalUser {
                    doc /* Nancy Nightingale, discharge nurse. [ST-213, ST-054] */
                    perform searchForPatient;
                    perform reviewListAndDecideSamePerson;
                    perform requestMergeNewerToOlder;
                }
                actor identificationService {
                    doc /* The Identification Service instance. [ST-001] */
                    perform returnPersonListWithTwoAdams;
                    perform acknowledgeMerge;
                }
                objective {
                    doc /* Merge two identity records, deprecating the newer and
                         * retaining only the surviving record for future use. */
                }
                /* Step 1: Nancy searches Adam */
                action searchForPatient;
                /* Step 2: HIS calls FindIdentityByProperty(Adam) on IS */
                action relaySearchToIS;
                /* Step 3: IS returns person list including two Adams */
                action returnPersonListWithTwoAdams;
                /* Step 4: HIS displays person list to Nancy */
                action displayPersonList;
                /* Step 5: Nancy reviews, decides two Adams are same person */
                action reviewListAndDecideSamePerson;
                /* Step 6: Nancy requests merge newer Adam to older Adam */
                action requestMergeNewerToOlder;
                /* Step 7: HIS calls MergeIdentities(Person, newerAdam, Person, olderAdam) on IS */
                action relayMergeRequestToIS;
                /* Step 8: IS returns acknowledgement */
                action acknowledgeMerge;
                /* Step 9: HIS confirms identity merged to Nancy */
                action confirmIdentityMerged;
                ref first start then searchForPatient;
                ref first searchForPatient then relaySearchToIS;
                ref first relaySearchToIS then returnPersonListWithTwoAdams;
                ref first returnPersonListWithTwoAdams then displayPersonList;
                ref first displayPersonList then reviewListAndDecideSamePerson;
                ref first reviewListAndDecideSamePerson then requestMergeNewerToOlder;
                ref first requestMergeNewerToOlder then relayMergeRequestToIS;
                ref first relayMergeRequestToIS then acknowledgeMerge;
                ref first acknowledgeMerge then confirmIdentityMerged;
                ref first confirmIdentityMerged then done;
            }

            /* --- Scenario 3: Update Demographics (SFM 3.2.3) --- */

            include use case updateDemographics {
                doc /* Adam returns to the hospital. Carol cannot find an exact match
                     * but recognizes Adam after checking DOB and qualifying questions.
                     * She discovers his address is out of date, updates demographics,
                     * and submits the change to IS via a Link operation.
                     * [ST-056, ST-057, ST-058] */

                subject hospitalInformationSystem {
                    doc /* The clinical system mediating between the clerk and the
                         * Identification Service. [ST-045] */
                    perform relaySearchToIS;
                    perform displayPersonList;
                    perform relayLinkUpdateToIS;
                    perform confirmDemographicsUpdated;
                }
                actor registrationClerk {
                    doc /* Carol Clerk. [ST-212, ST-056] */
                    perform searchPatient;
                    perform reviewListRecognizeOutdatedAddress;
                    perform updateDemographicValues;
                }
                actor identificationService {
                    doc /* The Identification Service instance. [ST-001] */
                    perform returnPersonListIncludingPatient;
                    perform acknowledgeLinkUpdate;
                }
                objective {
                    doc /* Locate an existing identity with outdated demographic information
                         * and update the identifying properties to reflect current data. */
                }
                /* Step 1: Carol searches Adam */
                action searchPatient;
                /* Step 2: HIS calls FindIdentityByProperty(Person, Adam) on IS */
                action relaySearchToIS;
                /* Step 3: IS returns person list including Adam */
                action returnPersonListIncludingPatient;
                /* Step 4: HIS displays person list to Carol */
                action displayPersonList;
                /* Step 5: Carol reviews list, recognizes address is out of date */
                action reviewListRecognizeOutdatedAddress;
                /* Step 6: Carol updates demographic values (address, phone) */
                action updateDemographicValues;
                /* Step 7: HIS calls LinkIdentities(Person, newerAdam, Person, olderAdam) on IS */
                action relayLinkUpdateToIS;
                /* Step 8: IS returns acknowledgement */
                action acknowledgeLinkUpdate;
                /* Step 9: HIS confirms demographics updated to Carol */
                action confirmDemographicsUpdated;
                ref first start then searchPatient;
                ref first searchPatient then relaySearchToIS;
                ref first relaySearchToIS then returnPersonListIncludingPatient;
                ref first returnPersonListIncludingPatient then displayPersonList;
                ref first displayPersonList then reviewListRecognizeOutdatedAddress;
                ref first reviewListRecognizeOutdatedAddress then updateDemographicValues;
                ref first updateDemographicValues then relayLinkUpdateToIS;
                ref first relayLinkUpdateToIS then acknowledgeLinkUpdate;
                ref first acknowledgeLinkUpdate then confirmDemographicsUpdated;
                ref first confirmDemographicsUpdated then done;
            }

            /* --- Scenario 4: Inactivate Entity (SFM 3.2.4) --- */

            include use case inactivateEntity {
                doc /* Per company policy (death, relocation, plan change, test data
                     * removal, etc.), Carol changes Adam's entity state to Inactive.
                     * He will not appear in clinical searches but remains accessible
                     * to administrators. [ST-059, ST-060, ST-061] */

                subject hospitalInformationSystem {
                    doc /* The clinical system relaying the state change to the
                         * Identification Service. [ST-045] */
                    perform relayInactivationToIS;
                    perform confirmInactivation;
                }
                actor serviceAdministrator {
                    doc /* Carol Clerk acting in administrator capacity. [ST-215, ST-059] */
                    perform requestInactivation;
                }
                actor identificationService {
                    doc /* The Identification Service instance. [ST-001] */
                    perform acknowledgeInactivation;
                }
                objective {
                    doc /* Change an identity's state to inactive so it no longer appears
                         * in general clinical searches while remaining accessible to
                         * administrators. */
                }
                /* Step 1: Carol requests inactivation of Adam's record */
                action requestInactivation;
                /* Step 2: HIS calls UpdateIdentityStatus(Person, EntityID, Inactive) on IS */
                action relayInactivationToIS;
                /* Step 3: IS returns acknowledgement */
                action acknowledgeInactivation;
                /* Step 4: HIS confirms inactivation to Carol */
                action confirmInactivation;
                ref first start then requestInactivation;
                ref first requestInactivation then relayInactivationToIS;
                ref first relayInactivationToIS then acknowledgeInactivation;
                ref first acknowledgeInactivation then confirmInactivation;
                ref first confirmInactivation then done;
            }

            /* --- Scenario 5: Activate Entity (SFM 3.2.5) --- */

            include use case activateEntity {
                doc /* Carol realizes the inactivation was a mistake. She finds Adam's
                     * entry via IS admin search and changes state back to Active.
                     * [ST-062, ST-063] */

                subject hospitalInformationSystem {
                    doc /* The clinical system relaying the state change to the
                         * Identification Service. [ST-045] */
                    perform relayActivationToIS;
                    perform confirmActivation;
                }
                actor serviceAdministrator {
                    doc /* Carol Clerk acting in administrator capacity. [ST-215, ST-062] */
                    perform requestActivation;
                }
                actor identificationService {
                    doc /* The Identification Service instance. [ST-001] */
                    perform acknowledgeActivation;
                }
                objective {
                    doc /* Restore a previously inactivated identity to active state,
                         * allowing it to appear in general clinical searches again. */
                }
                /* Step 1: Carol requests activation of Adam's record */
                action requestActivation;
                /* Step 2: HIS calls UpdateIdentityStatus(Person, EntityID, Active) on IS */
                action relayActivationToIS;
                /* Step 3: IS returns acknowledgement */
                action acknowledgeActivation;
                /* Step 4: HIS confirms activation to Carol */
                action confirmActivation;
                ref first start then requestActivation;
                ref first requestActivation then relayActivationToIS;
                ref first relayActivationToIS then acknowledgeActivation;
                ref first acknowledgeActivation then confirmActivation;
                ref first confirmActivation then done;
            }

            /* --- Scenario 6: Unlink (Unmerge) Entity (SFM 3.2.6) --- */

            include use case unlinkEntity {
                doc /* Miss Evelyn Smith enters the hospital. Carol discovers she was
                     * erroneously linked to Mrs. Eve Everywoman (whose maiden name
                     * was Smith). Carol retrieves aliases, identifies the mistake,
                     * unlinks the erroneous alias, and proceeds with admission.
                     * [ST-064, ST-065, ST-066, ST-067] */

                subject hospitalInformationSystem {
                    doc /* The clinical system mediating between the clerk and the
                         * Identification Service. [ST-045] */
                    perform relaySearchToIS;
                    perform displayPersonList;
                    perform relayListLinkedToIS;
                    perform displayAliasList;
                    perform relayUnlinkToIS;
                    perform confirmUnlink;
                }
                actor registrationClerk {
                    doc /* Carol Clerk investigating linked records. [ST-212, ST-064] */
                    perform searchEvelynSmith;
                    perform reviewPersonList_discoverHistoricalLink;
                    perform requestRetrieveAllAliases;
                    perform reviewAliasList_identifyMistake;
                    perform requestUnlinkAlias;
                    perform proceedWithAdmission;
                }
                actor identificationService {
                    doc /* The Identification Service instance. [ST-001] */
                    perform returnPersonListTwoSmiths;
                    perform returnAliasList;
                    perform acknowledgeUnlinking;
                }
                objective {
                    doc /* Remove an erroneous link between two identity instances,
                         * restoring them as distinct entities. */
                }
                /* Step 1: Carol searches Miss Evelyn Smith */
                action searchEvelynSmith;
                /* Step 2: HIS calls FindIdentityByProperties(Person, Smith, Evelyn, F) on IS */
                action relaySearchToIS;
                /* Step 3: IS returns person list including two Smiths */
                action returnPersonListTwoSmiths;
                /* Step 4: HIS displays person list to Carol */
                action displayPersonList;
                /* Step 5: Carol reviews — Evelyn Smith has historical records matched to Eve Everywoman */
                action reviewPersonList_discoverHistoricalLink;
                /* Step 6: Carol requests retrieve all aliases of Eve Everywoman */
                action requestRetrieveAllAliases;
                /* Step 7: HIS calls ListLinkedIdentities(Person, EntityID) on IS */
                action relayListLinkedToIS;
                /* Step 8: IS returns alias list of Eve Everywoman */
                action returnAliasList;
                /* Step 9: HIS displays alias list to Carol */
                action displayAliasList;
                /* Step 10: Carol reviews alias list — decides Evelyn Smith was mistakenly linked */
                action reviewAliasList_identifyMistake;
                /* Step 11: Carol requests unlink alias Smith from Everywoman */
                action requestUnlinkAlias;
                /* Step 12: HIS calls UnlinkIdentity(Person, Smith, Person, Everywoman) on IS */
                action relayUnlinkToIS;
                /* Step 13: IS acknowledges unlinking */
                action acknowledgeUnlinking;
                /* Step 14: HIS confirms unlink to Carol */
                action confirmUnlink;
                /* Step 15-16: Carol proceeds with Smith's admission */
                action proceedWithAdmission;
                ref first start then searchEvelynSmith;
                ref first searchEvelynSmith then relaySearchToIS;
                ref first relaySearchToIS then returnPersonListTwoSmiths;
                ref first returnPersonListTwoSmiths then displayPersonList;
                ref first displayPersonList then reviewPersonList_discoverHistoricalLink;
                ref first reviewPersonList_discoverHistoricalLink then requestRetrieveAllAliases;
                ref first requestRetrieveAllAliases then relayListLinkedToIS;
                ref first relayListLinkedToIS then returnAliasList;
                ref first returnAliasList then displayAliasList;
                ref first displayAliasList then reviewAliasList_identifyMistake;
                ref first reviewAliasList_identifyMistake then requestUnlinkAlias;
                ref first requestUnlinkAlias then relayUnlinkToIS;
                ref first relayUnlinkToIS then acknowledgeUnlinking;
                ref first acknowledgeUnlinking then confirmUnlink;
                ref first confirmUnlink then proceedWithAdmission;
                ref first proceedWithAdmission then done;
            }

            /* --- Scenario 7a: Look Up a Patient — Single Entry Found (SFM 3.2.7a) --- */

            include use case lookupSingleEntry {
                doc /* Pre-op nurse Clarence Barton looks up Adam's records in HIS
                     * (which queries IS). A single match is found. Clarence locates
                     * the surgical encounter and records vital signs.
                     * [ST-181, ST-182] */

                subject hospitalInformationSystem {
                    doc /* The clinical system relaying the search to the Identification
                         * Service. [ST-045] */
                    perform relaySearchToIS;
                    perform displayPatientRecord;
                }
                actor clinicalUser {
                    doc /* Clarence Barton, pre-op nurse. [ST-213, ST-181] */
                    perform searchPatient;
                    perform locateSurgicalEncounter;
                    perform enterVitalSigns;
                }
                actor identificationService {
                    doc /* The Identification Service instance. [ST-001] */
                    perform returnSingleMatch;
                }
                objective {
                    doc /* Find a specific patient identity from identifying properties
                         * and retrieve the associated clinical encounter. */
                }
                /* Step 1: Clarence searches Adam */
                action searchPatient;
                /* Step 2: HIS calls FindIdentityByProperties(Person, Adam) on IS */
                action relaySearchToIS;
                /* Step 3: IS returns single match (Adam) */
                action returnSingleMatch;
                /* Step 4: HIS displays Adam's record to Clarence */
                action displayPatientRecord;
                /* Step 5: Clarence locates Adam's surgical encounter */
                action locateSurgicalEncounter;
                /* Step 6: Clarence enters Adam's vital signs */
                action enterVitalSigns;
                ref first start then searchPatient;
                ref first searchPatient then relaySearchToIS;
                ref first relaySearchToIS then returnSingleMatch;
                ref first returnSingleMatch then displayPatientRecord;
                ref first displayPatientRecord then locateSurgicalEncounter;
                ref first locateSurgicalEncounter then enterVitalSigns;
                ref first enterVitalSigns then done;
            }

            /* --- Scenario 7b: Look Up a Patient — Multiple Entries Found (SFM 3.2.7b) --- */

            include use case lookupMultipleEntries {
                doc /* Adam enters for an outpatient appointment. Multiple matches are
                     * returned. Carol narrows the list with additional criteria (age,
                     * address), identifies the correct Adam using quality/confidence
                     * attributes, and creates a new encounter.
                     * [ST-183, ST-184] */

                subject hospitalInformationSystem {
                    doc /* The clinical system relaying searches to the Identification
                         * Service. [ST-045] */
                    perform relayInitialSearchToIS;
                    perform displayAllEntries;
                    perform relayRefinedSearchToIS;
                    perform displayShorterList;
                }
                actor registrationClerk {
                    doc /* Carol Clerk. [ST-212, ST-183] */
                    perform searchPatient;
                    perform enterAdditionalCriteria;
                    perform selectCorrectPatient;
                    perform createNewEncounter;
                }
                actor identificationService {
                    doc /* The Identification Service instance. [ST-001] */
                    perform returnMultipleMatches;
                    perform returnShorterList;
                }
                objective {
                    doc /* Progressively refine a search to correctly identify a
                         * patient from among multiple candidate matches. */
                }
                /* Step 1: Carol searches Adam */
                action searchPatient;
                /* Step 2: HIS calls FindIdentityByProperties(Person, Adam) on IS */
                action relayInitialSearchToIS;
                /* Step 3: IS returns list including Adam (multiple matches) */
                action returnMultipleMatches;
                /* Step 4: HIS displays all entries to Carol */
                action displayAllEntries;
                /* Step 5: Carol enters additional criteria (age, address) */
                action enterAdditionalCriteria;
                /* Step 6: HIS calls FindIdentityByProperties(Person, Adam, Age, Address) on IS */
                action relayRefinedSearchToIS;
                /* Step 7: IS returns shorter person list including Adam */
                action returnShorterList;
                /* Step 8: HIS displays shorter list to Carol */
                action displayShorterList;
                /* Step 9: Carol selects the correct Adam */
                action selectCorrectPatient;
                /* Step 10-11: Carol creates a new encounter for Adam */
                action createNewEncounter;
                ref first start then searchPatient;
                ref first searchPatient then relayInitialSearchToIS;
                ref first relayInitialSearchToIS then returnMultipleMatches;
                ref first returnMultipleMatches then displayAllEntries;
                ref first displayAllEntries then enterAdditionalCriteria;
                ref first enterAdditionalCriteria then relayRefinedSearchToIS;
                ref first relayRefinedSearchToIS then returnShorterList;
                ref first returnShorterList then displayShorterList;
                ref first displayShorterList then selectCorrectPatient;
                ref first selectCorrectPatient then createNewEncounter;
                ref first createNewEncounter then done;
            }

            /* --- Scenario 7c: Look Up a Patient — Merged Entries Found (SFM 3.2.7c) --- */

            include use case mergedEntriesFound {
                doc /* Bill Beaker adds a lab test using an old identifier that has
                     * been merged. IS returns the merged indication plus the active
                     * surviving identifier. Bill updates the lab test with the
                     * correct identifier. [ST-185, ST-186] */

                subject hospitalInformationSystem {
                    doc /* The clinical system mediating between the laboratory clerk
                         * and the Identification Service. [ST-045] */
                    perform relayIdentifierLookupToIS;
                    perform displayMergedIdentifier;
                }
                actor laboratoryClerk {
                    doc /* Bill Beaker. [ST-046, ST-185] */
                    perform enterLabTestWithOldIdentifier;
                    perform updateLabTestWithCorrectIdentifier;
                }
                actor identificationService {
                    doc /* The Identification Service instance. [ST-001] */
                    perform returnMergedIndication;
                }
                objective {
                    doc /* Detect that a supplied identifier has been deprecated through
                         * a merge and redirect to the surviving active identifier. */
                }
                /* Step 1: Bill enters lab test with Adam's old identifier */
                action enterLabTestWithOldIdentifier;
                /* Step 2: HIS calls GetAllInformationForIdentity(Person, AdamIdentifier) on IS */
                action relayIdentifierLookupToIS;
                /* Step 3: IS returns merged identifier indication + surviving ID */
                action returnMergedIndication;
                /* Step 4: HIS shows merged identifier to Bill */
                action displayMergedIdentifier;
                /* Step 5-6: Bill updates lab test with correct identifier */
                action updateLabTestWithCorrectIdentifier;
                ref first start then enterLabTestWithOldIdentifier;
                ref first enterLabTestWithOldIdentifier then relayIdentifierLookupToIS;
                ref first relayIdentifierLookupToIS then returnMergedIndication;
                ref first returnMergedIndication then displayMergedIdentifier;
                ref first displayMergedIdentifier then updateLabTestWithCorrectIdentifier;
                ref first updateLabTestWithCorrectIdentifier then done;
            }

            /* --- Scenario 8: Unattended Encounter (SFM 3.2.8) --- */

            include use case unattendedEncounter {
                doc /* A referral system receives an HL7 message from another
                     * institution for an unknown patient. The system queries IS to
                     * resolve identity. Four alternative outcomes:
                     * (1) match found — processing continues;
                     * (2) multiple possible matches — needs human review;
                     * (3) no match — system auto-creates a new identity;
                     * (4) no match — system awaits user instruction.
                     * Main flow models the happy path (Alt 1) with auto-create
                     * fallback (Alt 3). [ST-187, ST-188, ST-189, ST-190, ST-191] */

                subject referralSystem {
                    doc /* The referral system attempting to resolve a patient identity
                         * from incoming referral information. [ST-187] */
                    perform receiveExternalReferral;
                    perform requestPatientIdentifier;
                    perform handleResolutionOutcome;
                }
                actor externalSystem {
                    doc /* The external institution sending the HL7 referral message.
                         * [ST-187] */
                    perform sendHL7ReferralMessage;
                }
                actor identificationService {
                    doc /* The Identification Service instance. [ST-001] */
                    perform findPatientIdentifier;
                    perform returnPatientIdentifier;
                }
                objective {
                    doc /* Automatically resolve the identity of a referred patient
                         * or determine the appropriate fallback action when automatic
                         * resolution is not possible. */
                }
                /* Step 1: External system sends HL7 referral message to Referrals */
                action sendHL7ReferralMessage;
                /* Step 2: Referral system receives and extracts patient info */
                action receiveExternalReferral;
                /* Step 3: Referral system requests patient identifier from IS */
                action requestPatientIdentifier;
                /* Step 4: IS attempts to find patient identifier */
                action findPatientIdentifier;
                /* Step 5: Referral system handles outcome (match/create/manual) */
                action handleResolutionOutcome;
                /* Step 6: IS returns patient identifier */
                action returnPatientIdentifier;
                ref first start then sendHL7ReferralMessage;
                ref first sendHL7ReferralMessage then receiveExternalReferral;
                ref first receiveExternalReferral then requestPatientIdentifier;
                ref first requestPatientIdentifier then findPatientIdentifier;
                ref first findPatientIdentifier then handleResolutionOutcome;
                ref first handleResolutionOutcome then returnPatientIdentifier;
                ref first returnPatientIdentifier then done;
            }

            /* --- Scenario 9: Remove Entity from the System (SFM 3.2.9) --- */

            include use case removeEntity {
                doc /* Carol created a pseudo-record for testing. After testing, she
                     * finds the record and permanently purges it from IS. The record
                     * may be kept for audit trail purposes but is no longer findable.
                     * [ST-192, ST-193, ST-194] */

                subject hospitalInformationSystem {
                    doc /* The clinical system relaying the removal request to the
                         * Identification Service. [ST-045] */
                    perform relayRemovalToIS;
                    perform confirmRemoval;
                }
                actor serviceAdministrator {
                    doc /* Carol Clerk with administrative privileges. [ST-215, ST-192] */
                    perform requestRemoval;
                }
                actor identificationService {
                    doc /* The Identification Service instance. [ST-001] */
                    perform acknowledgeRemoval;
                }
                objective {
                    doc /* Permanently remove a fictitious or test identity from the
                         * service so it is no longer discoverable. */
                }
                /* Step 1: Carol requests removal of Bob's record */
                action requestRemoval;
                /* Step 2: HIS calls RemoveIdentity(Person, EntityID) on IS */
                action relayRemovalToIS;
                /* Step 3: IS returns acknowledgement */
                action acknowledgeRemoval;
                /* Step 4: HIS confirms removal to Carol */
                action confirmRemoval;
                ref first start then requestRemoval;
                ref first requestRemoval then relayRemovalToIS;
                ref first relayRemovalToIS then acknowledgeRemoval;
                ref first acknowledgeRemoval then confirmRemoval;
                ref first confirmRemoval then done;
            }
        }

        /* -----------------------------------------------------------
         * Multi-Domain Scenarios (Section 3.3)
         * ----------------------------------------------------------- */

        part multiDomainScenarios {
            doc /* Business scenarios involving multiple PolicyDomains, illustrating
                 * cross-organizational identity resolution and linking. Setting:
                 * Solar System Healthcare with 4 regions (East, West, North, South),
                 * hospitals Jupiter, Orion, Moon, Good Health — each with its own IS.
                 * A master national XIS (Cross-community Identification Service)
                 * operates cross-references. These are non-normative.
                 * [ST-195, ST-202] */

            /* --- Scenario 10: Look Up Across a Regional Network (SFM 3.3.1) --- */

            include use case lookupAcrossRegionalNetwork {
                doc /* Adam normally receives care at Good Health Hospital. While on
                     * vacation, he is admitted to Jupiter Hospital. Carol cannot find
                     * Adam locally, so she requests a search across the RHIO network.
                     * Good Health's IS finds a match and returns Adam's identifier.
                     * [ST-196, ST-197] */

                subject localIdentificationService {
                    doc /* IS at Orion/Jupiter Hospital, the local IS that receives
                         * Carol's search and forwards to XIS. [ST-001, ST-196] */
                    perform forwardSearchToXIS;
                    perform returnPatientToClerk;
                }
                actor registrationClerk {
                    doc /* Carol Clerk at Jupiter Hospital. [ST-212, ST-196] */
                    perform searchPatientLocally;
                }
                actor crossCommunityIdentificationService {
                    doc /* XIS_RHIO — the regional cross-community Identification
                         * Service that federates search across member IS instances.
                         * [ST-035, ST-196] */
                    perform federateSearchAcrossMembers;
                    perform returnAggregatedResult;
                }
                actor memberIdentificationService {
                    doc /* IS at Good Health Hospital (or other member hospitals)
                         * responding to the federated search. [ST-001, ST-197] */
                    perform searchLocalRegistry;
                    perform returnMatchFromRemoteHospital;
                }
                objective {
                    doc /* Locate a patient's identity across the regional health
                         * network when the patient is not found locally. */
                }
                /* Step 1: Carol searches Adam at local IS_Orion */
                action searchPatientLocally;
                /* Step 2: IS_Orion forwards FindIdentityByProperty(Person, Adam) to XIS_RHIO */
                action forwardSearchToXIS;
                /* Step 3: XIS_RHIO broadcasts FindIdentityByProperty(Person, Adam) to member IS instances */
                action federateSearchAcrossMembers;
                /* Step 4: Member IS searches local registry */
                action searchLocalRegistry;
                /* Step 4 cont: IS_GoodHealth returns Adam (from Hospital Moon) to XIS */
                action returnMatchFromRemoteHospital;
                /* Step 5: XIS_RHIO returns aggregated result to IS_Orion */
                action returnAggregatedResult;
                /* Step 6: IS_Orion returns Adam to Carol */
                action returnPatientToClerk;
                ref first start then searchPatientLocally;
                ref first searchPatientLocally then forwardSearchToXIS;
                ref first forwardSearchToXIS then federateSearchAcrossMembers;
                ref first federateSearchAcrossMembers then searchLocalRegistry;
                ref first searchLocalRegistry then returnMatchFromRemoteHospital;
                ref first returnMatchFromRemoteHospital then returnAggregatedResult;
                ref first returnAggregatedResult then returnPatientToClerk;
                ref first returnPatientToClerk then done;
            }

            /* --- Scenario 11: Look Up Specifying a Specific External Organization (SFM 3.3.2) --- */

            include use case lookupAtSpecificOrganization {
                doc /* Eve Everywoman is admitted to Level Seven Healthcare with an
                     * ankle injury. She tells Carol she is a Good Health patient.
                     * Carol searches IS specifying the target organization. The
                     * request goes through XIS_RHIO to Orion's IS, which locates
                     * Eve's record. [ST-198, ST-199] */

                subject localIdentificationService {
                    doc /* IS at Moon Hospital, the local IS receiving Carol's
                         * directed search. [ST-001, ST-198] */
                    perform forwardDirectedSearchToXIS;
                    perform returnPatientToClerk;
                }
                actor registrationClerk {
                    doc /* Carol Clerk at Level Seven Healthcare, specifying Orion/Good
                         * Health Hospital as the target. [ST-212, ST-198] */
                    perform searchPatientSpecifyingOrganization;
                }
                actor crossCommunityIdentificationService {
                    doc /* XIS_RHIO directing the search to a specific organization.
                         * [ST-035, ST-198] */
                    perform forwardSearchToTargetOrganization;
                    perform returnDirectedResult;
                }
                actor targetIdentificationService {
                    doc /* IS at Orion/Good Health Hospital responding to the directed
                         * search. [ST-001, ST-199] */
                    perform searchTargetRegistry;
                    perform returnMatchFromTargetHospital;
                }
                objective {
                    doc /* Locate a patient's identity at a specifically designated
                         * external organization. */
                }
                /* Step 1: Carol searches Eve, specifying Orion as target */
                action searchPatientSpecifyingOrganization;
                /* Step 2: IS_Moon forwards FindIdentityByProperty(Person, Eve, Orion) to XIS_RHIO */
                action forwardDirectedSearchToXIS;
                /* Step 3: XIS_RHIO forwards FindIdentityByProperty(Person, Eve) to IS_Orion */
                action forwardSearchToTargetOrganization;
                /* Step 4: IS_Orion searches local registry */
                action searchTargetRegistry;
                /* Step 4 cont: IS_Orion returns Eve to XIS_RHIO */
                action returnMatchFromTargetHospital;
                /* Step 5: XIS_RHIO returns Eve to IS_Moon */
                action returnDirectedResult;
                /* Step 6: IS_Moon returns Eve to Carol */
                action returnPatientToClerk;
                ref first start then searchPatientSpecifyingOrganization;
                ref first searchPatientSpecifyingOrganization then forwardDirectedSearchToXIS;
                ref first forwardDirectedSearchToXIS then forwardSearchToTargetOrganization;
                ref first forwardSearchToTargetOrganization then searchTargetRegistry;
                ref first searchTargetRegistry then returnMatchFromTargetHospital;
                ref first returnMatchFromTargetHospital then returnDirectedResult;
                ref first returnDirectedResult then returnPatientToClerk;
                ref first returnPatientToClerk then done;
            }

            /* --- Scenario 12: Link Entities Across Regions (SFM 3.3.3) --- */

            include use case linkEntitiesAcrossRegions {
                doc /* Adam is admitted to Jupiter Hospital (North region). Eric Entry
                     * cannot find Adam locally. Adam says he is a Solar System patient
                     * elsewhere. Eric requests a cross-organization search. The national
                     * XIS finds Adam from the East region. A new identifier is created
                     * in the North region and linked to the master XIS identifier.
                     * [ST-200, ST-201] */

                subject hospitalInformationSystem {
                    doc /* HIS at Jupiter Hospital mediating between Eric and the
                         * regional IS. [ST-045, ST-200] */
                    perform relayLocalSearchToIS;
                    perform reportNoLocalMatch;
                    perform relayCrossOrgSearchToIS;
                    perform returnPatientToClerk;
                }
                actor registrationClerk {
                    doc /* Eric Entry at Jupiter Hospital. [ST-212, ST-200] */
                    perform searchPatientLocally;
                    perform searchPatientAcrossOrganization;
                }
                actor regionalIdentificationService {
                    doc /* IS_North — the regional IS for the North region. [ST-001, ST-200] */
                    perform searchLocalRegistry;
                    perform returnNoLocalMatch;
                    perform federateSearchToXIS;
                    perform registerNewLocalIdentity;
                    perform linkLocalIdentityToMaster;
                    perform returnPatientToHIS;
                }
                actor nationalCrossReferenceService {
                    doc /* XIS_SolarSystem — the national cross-reference service
                         * managing master identifiers. [ST-035, ST-200] */
                    perform searchNationalRegistry;
                    perform returnPatientFromRemoteRegion;
                    perform acknowledgeCrossRegionLink;
                }
                objective {
                    doc /* Create a new local identity for a patient found in another
                         * region and link it to the master cross-reference identifier
                         * in the national service. */
                }
                /* Step 1: Eric searches Adam locally */
                action searchPatientLocally;
                /* Step 2: HIS calls FindIdentityByProperty(Patient, Adam) on IS_North */
                action relayLocalSearchToIS;
                /* Step 3: IS_North searches local registry — no match */
                action searchLocalRegistry;
                /* Step 3 cont: IS_North returns no match to HIS */
                action returnNoLocalMatch;
                /* Step 4: HIS reports no match found to Eric */
                action reportNoLocalMatch;
                /* Step 5: Eric requests search across SolarSystem organization */
                action searchPatientAcrossOrganization;
                /* Step 6: HIS calls FindIdentityByProperty(Patient, Adam, SolarSystem) on IS_North */
                action relayCrossOrgSearchToIS;
                /* Step 7: IS_North federates FindIdentityByProperty(Patient, Adam) to XIS_SolarSystem */
                action federateSearchToXIS;
                /* Step 8: XIS_SolarSystem searches national registry and returns Adam from East region */
                action searchNationalRegistry;
                action returnPatientFromRemoteRegion;
                /* Step 9: IS_North creates new local identifier for Adam */
                action registerNewLocalIdentity;
                /* Step 10: IS_North calls LinkIdentity (ties new regional ID to master ID) on XIS */
                action linkLocalIdentityToMaster;
                /* Step 11: XIS_SolarSystem acknowledges cross-region link */
                action acknowledgeCrossRegionLink;
                /* Step 12: IS_North returns Adam to HIS */
                action returnPatientToHIS;
                /* Step 13: HIS returns Adam to Eric */
                action returnPatientToClerk;
                ref first start then searchPatientLocally;
                ref first searchPatientLocally then relayLocalSearchToIS;
                ref first relayLocalSearchToIS then searchLocalRegistry;
                ref first searchLocalRegistry then returnNoLocalMatch;
                ref first returnNoLocalMatch then reportNoLocalMatch;
                ref first reportNoLocalMatch then searchPatientAcrossOrganization;
                ref first searchPatientAcrossOrganization then relayCrossOrgSearchToIS;
                ref first relayCrossOrgSearchToIS then federateSearchToXIS;
                ref first federateSearchToXIS then searchNationalRegistry;
                ref first searchNationalRegistry then returnPatientFromRemoteRegion;
                ref first returnPatientFromRemoteRegion then registerNewLocalIdentity;
                ref first registerNewLocalIdentity then linkLocalIdentityToMaster;
                ref first linkLocalIdentityToMaster then acknowledgeCrossRegionLink;
                ref first acknowledgeCrossRegionLink then returnPatientToHIS;
                ref first returnPatientToHIS then returnPatientToClerk;
                ref first returnPatientToClerk then done;
            }
        }
    }
}
